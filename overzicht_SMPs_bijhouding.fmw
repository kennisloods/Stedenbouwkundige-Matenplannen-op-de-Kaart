FME workspace overzicht_SMPs_bijhouding.fmw

Parameters:
- P_SMP_FGDB = K:\GEODATA\Kennisloods\Data\Uitzendingen_overzicht\Uitzendingen_overzicht.gdb   # File Geodatabase
- P_BRON_TEKENINGPAD = K:/SO/RW/Algemeen/UITZENDINGEN NIEUWE STIJL/2 SMP   # Source Folder and File Pathnames Folder
- P_BRON_UITZENDINGEN_XLS = K:\SO\RW\Algemeen\UITZENDINGEN NIEUWE STIJL\2 SMP\001 Sjablonen\Schema Voortgang SMP def.xlsx   # Source Microsoft Excel File(s)
- P_BRON_UITZENDINGEN_CSV = $(FME_MF_DIR)Schema Voortgang SMP def.csv   # Source CSV (Comma Separated Value) File(s)
- P_BRON_TIR_GEMEENTE_SHP = K:\GEODATA\Basisdata\TIR\Data\SHP\Gemeente\Gemeente_vlakken.shp   # Source Esri Shapefile(s)
- P_DOEL_BACKUP_FOLDER = K:\GEODATA\Kennisloods\Data\Uitzendingen_overzicht\backup   # BAckupfolder
- P_DOEL_UITVAL_FOLDER = K:\GEODATA\Kennisloods\Data\Uitzendingen_overzicht\uitval   # Uitvalfolder
- P_LOG = $(FME_MF_DIR)log\overzicht_SMPs_bijhouding.log   # Log File

Readers:
- PATH_1: PATH from $(P_BRON_TEKENINGPAD)
- ESRISHAPE_1: ESRISHAPE from $(P_BRON_TIR_GEMEENTE_SHP) in EPSG:28992
- GEODATABASE_FILE_1: GEODATABASE_FILE from $(P_SMP_FGDB) in EPSG:28992
- XLSXR_1: XLSXR from $(P_BRON_UITZENDINGEN_XLS)
- CSV2_1: CSV2 from $(P_BRON_UITZENDINGEN_CSV)

Writers:
- GEODATABASE_FILE_2: GEODATABASE_FILE to $(P_SMP_FGDB) in EPSG:28992
- GEODATABASE_FILE_3: GEODATABASE_FILE to $(P_DOEL_BACKUP_FOLDER) in EPSG:28992
- XLSXW_1: XLSXW to $(P_DOEL_UITVAL_FOLDER)

Note: inlezen paden / bestandsnamen / van dwg's in SMP-map
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> AttributeKeeper_Path
StringPairReplacer_2_OUTPUT_-__FeatureMerger_UitzendingMetTekening_REQUESTOR: Junction
    -> FeatureMerger_UitzendingMetTekening [REQUESTOR]
    -> InlineQuerierTekening [Tekeningenlijst]
Note: in tekeningnummer '-' vervangen / door '/' / bijv. 18-00046 wordt 18/00046
StringPairReplacer
    MAP = - /
    RESULT_ATTR = _tekeningnummer
    SRC_ATTR = _tekeningnummer
    CASE = no
    -> AttributeValueMapper_2
Note: IJS wordt YS
AttributeValueMapper_2
    VAL_ATTR = _gebiedcode
    DEFAULT_VALUE = @Value(_gebiedcode)
    LUT = IJS,YS
    DIRECTION = Forward (Source To Destination)
    SRC = _gebiedcode
    -> StringPairReplacer_OUTPUT_-__Tester_VerzenddatumVUZHasValue
Note: inlezen bestaande set
SMP_overzicht (reader GEODATABASE_FILE_1)
    attributes: OBJECTID integer, projectnaam char(50), tekeningnummer char(50), stedenbouwkundige char(50), SHAPE_Length double, SHAPE_Area double, landschapsarchitect char(50), tekenaar char(50), fase smallint, revisie smallint, actueel smallint, projectmanager char(50), bestandsactualisatie date, identificatie guid, programma char(50), geplandeStartdatumBouw date, datumOpmaak date, datumUitzending date, tekeningfolder char(500), tekeningPDF char(500), opmerking char(50), bronMetadata char(500), gebiedcode char(3), gebiednaam char(500)
    -> Tester_revisie_hasValue
    -> SMP_overzicht (writer GEODATABASE_FILE_3)
Note: NieuweTekFase: tekeningnummer en/of / tekeningnummer + fase zijn nieuw / NieuweRevisie: tekeningnummer en fase komen in / de uitzendingenlijst en in SMP_overzicht voor, maar / in de tekeningenlijst komt een nieuwe revisie voor. / BestaandAfgesloten: tekeningnummer komt voor en / is actueel terwijl de uitzending is afgerond.
InlineQuerierTekening
    QUERY_DEF:
      NieuwTekFase,SELECT new."_gebiedcode"        AS gebiedcode
      ,      new."_tekeningnummer"    AS tekeningnummer
      ,      new."_fase"              AS fase
      ,      new."_datumUitzending"   AS datumUitzending
      ,      new."_projectnaam"       AS projectnaam
      ,      new."_stedenbouwkundige" AS stedenbouwkundige
      ,      new."_projectmanager"    AS projectmanager
      ,      new."_tekenaar"          AS tekenaar
      ,      new."_klaar"
      FROM  "Uitzendingenlijst" AS new
      WHERE NOT EXISTS ( SELECT 'x'
                         FROM   "SMP_overzicht" AS old
                         WHERE   new."_gebiedcode" = old."gebiedcode"
                         AND     new."_tekeningnummer" = old."tekeningnummer"
                         AND     new."_fase" = old."fase"
                       )
      ;,FIRST,NieuweRevisie,SELECT tek."_tekeningpad"
      ,      tek."_tekeningfolder"
      ,      tek."_revisie"           AS revisie
      ,      new."_gebiedcode"        AS gebiedcode
      ,      new."_tekeningnummer"    AS tekeningnummer
      ,      new."_fase"              AS fase
      ,      new."_datumUitzending"   AS datumUitzending
      ,      new."_projectnaam"       AS projectnaam
      ,      new."_stedenbouwkundige" AS stedenbouwkundige
      ,      new."_projectmanager"    AS projectmanager
      ,      new."_tekenaar"          AS tekenaar
      ,      new."_klaar"
      FROM   Tekeningenlijst   AS tek
      ,      Uitzendingenlijst AS new
      WHERE  new."_gebiedcode"     = tek."_gebiedcode"
      AND    new."_tekeningnummer" = tek."_tekeningnummer"
      AND    new."_fase"           = tek."_fase"
      AND    EXISTS     ( SELECT 'x'
                          FROM    SMP_overzicht AS old
      				    WHERE   old."gebiedcode"     = tek."_gebiedcode"
                          AND     old."tekeningnummer" = tek."_tekeningnummer"
                          AND     old."fase"           = tek."_fase"
      				   )
      AND    NOT EXISTS ( SELECT 'x'
                          FROM    SMP_overzicht AS old
      				    WHERE   old."gebiedcode"     = tek."_gebiedcode"
                          AND     old."tekeningnummer" = tek."_tekeningnummer"
                          AND     old."fase"           = tek."_fase"
      					AND     old."revisie"        = tek."_revisie"
      				   )
      ;,FIRST,BestaandAfgesloten,SELECT old."revisie"
      ,      old."projectnaam"
      ,      old."tekeningnummer"
      ,      old."stedenbouwkundige"
      ,      old."landschapsarchitect"
      ,      old."tekenaar"
      ,      old."fase"
      ,      old."actueel"
      ,      old."projectmanager"
      ,      old."bestandsactualisatie"
      ,      old."identificatie"
      ,      old."programma"
      ,      old."geplandeStartdatumBouw"
      ,      old."datumOpmaak"
      ,      old."datumUitzending"
      ,      old."tekeningfolder"
      ,      old."tekeningPDF"
      ,      old."opmerking"
      ,      old."bronMetadata"
      ,      old."gebiedcode"
      ,      old."gebiednaam"
      ,      new."_klaar"
      FROM   SMP_overzicht     AS old
      ,      Uitzendingenlijst AS new
      WHERE  new."_gebiedcode"     = old."gebiedcode"
      AND    new."_tekeningnummer" = old."tekeningnummer"
      AND    old."actueel" = 1
      AND    new."_klaar" IS NOT NULL
      ;,FIRST
    QUERY_SCHEMA = NieuwTekFase,gebiedcode,varchar(200),tekeningnummer,varchar(200),fase,varchar(200),datumUitzending,varchar(200),projectnaam,varchar(200),stedenbouwkundige,varchar(200),projectmanager,varchar(200),tekenaar,varchar(200),_klaar,varchar(200),NieuweRevisie,_tekeningpad,varchar(200),_tekeningfolder,varchar(200),revisie,varchar(200),gebiedcode,varchar(200),tekeningnummer,varchar(200),fase,varchar(200),datumUitzending,varchar(200),projectnaam,varchar(200),stedenbouwkundige,varchar(200),projectmanager,varchar(200),tekenaar,varchar(200),_klaar,varchar(200),BestaandAfgesloten,revisie,integer,projectnaam,varchar(50),tekeningnummer,varchar(50),stedenbouwkundige,varchar(50),landschapsarchitect,varchar(50),tekenaar,varchar(50),fase,integer,actueel,integer,projectmanager,varchar(50),bestandsactualisatie,text,identificatie,text,programma,varchar(50),geplandeStartdatumBouw,text,datumOpmaak,text,datumUitzending,text,tekeningfolder,varchar(500),tekeningPDF,varchar(500),opmerking,varchar(50),bronMetadata,varchar(500),gebiedcode,varchar(3),gebiednaam,varchar(500),_klaar,varchar(200)
    TABLE_DEF = Uitzendingenlijst,_tekeningnummer,varchar(200),_gebiedcode,varchar(200),_projectnaam,varchar(200),_stedenbouwkundige,varchar(200),_tekenaar,varchar(200),_projectmanager,varchar(200),_datumUitzending,varchar(200),_klaar,varchar(200),_fase,varchar(200),SMP_overzicht,revisie,integer,OBJECTID,integer,projectnaam,varchar(50),tekeningnummer,varchar(50),stedenbouwkundige,varchar(50),SHAPE_Length,float,SHAPE_Area,float,landschapsarchitect,varchar(50),tekenaar,varchar(50),fase,integer,actueel,integer,projectmanager,varchar(50),bestandsactualisatie,text,identificatie,text,programma,varchar(50),geplandeStartdatumBouw,text,datumOpmaak,text,datumUitzending,text,tekeningfolder,varchar(500),tekeningPDF,varchar(500),opmerking,varchar(50),bronMetadata,varchar(500),gebiedcode,varchar(3),gebiednaam,varchar(500),Tekeningenlijst,_gebiedcode,varchar(200),_tekeningnummer,varchar(200),_tekeningpad,varchar(200),_revisie,varchar(200),_fase,varchar(200),_tekeningfolder,varchar(200)
    NieuwTekFase -> FeatureMerger_UitzendingMetTekening [SUPPLIER]
    NieuwTekFase -> InlineQuerierPotentieelGewijzigd [NieuwTekFase]
    NieuweRevisie -> FeatureReader [INITIATOR]
    NieuweRevisie -> InlineQuerierPotentieelGewijzigd [NieuweRevisie]
    BestaandAfgesloten -> AttributeRenamer
Note: features waarbij een nieuwe / fase en/of revisie is / geintroduceerd. / Deze moeten worden bijgewerkt.
InlineQuerierPotentieelGewijzigd
    QUERY_DEF:
      potGewijzigd,SELECT old."revisie"
      ,      old."projectnaam"
      ,      old."tekeningnummer"
      ,      old."stedenbouwkundige"
      ,      old."landschapsarchitect"
      ,      old."tekenaar"
      ,      old."fase"
      ,      old."actueel"
      ,      old."projectmanager"
      ,      old."bestandsactualisatie"
      ,      old."identificatie"
      ,      old."programma"
      ,      old."geplandeStartdatumBouw"
      ,      old."datumOpmaak"
      ,      old."datumUitzending"
      ,      old."tekeningfolder"
      ,      old."tekeningPDF"
      ,      old."opmerking"
      ,      old."bronMetadata"
      ,      old."gebiedcode"
      ,      old."gebiednaam"
      FROM   "SMP_Overzicht" AS old
      WHERE EXISTS (SELECT 'x'
                    FROM  "NieuweRevisie" AS nre
                    WHERE nre."gebiedcode" = old."gebiedcode"
                    AND   nre."tekeningnummer" = old."tekeningnummer"
                    )
      OR    EXISTS (SELECT 'x'
                    FROM  "NieuwTekFase" AS nte
                    WHERE nte."gebiedcode" = old."gebiedcode"
                    AND   nte."tekeningnummer" = old."tekeningnummer"
                    )
       ;,FIRST
    QUERY_SCHEMA = potGewijzigd,revisie,integer,projectnaam,varchar(50),tekeningnummer,varchar(50),stedenbouwkundige,varchar(50),landschapsarchitect,varchar(50),tekenaar,varchar(50),fase,integer,actueel,integer,projectmanager,varchar(50),bestandsactualisatie,text,identificatie,text,programma,varchar(50),geplandeStartdatumBouw,text,datumOpmaak,text,datumUitzending,text,tekeningfolder,varchar(500),tekeningPDF,varchar(500),opmerking,varchar(50),bronMetadata,varchar(500),gebiedcode,varchar(3),gebiednaam,varchar(500)
    TABLE_DEF = NieuwTekFase,gebiedcode,varchar(3),tekeningnummer,varchar(50),fase,integer,datumUitzending,text,projectnaam,varchar(50),stedenbouwkundige,varchar(50),projectmanager,varchar(50),tekenaar,varchar(50),_klaar,varchar(200),NieuweRevisie,_tekeningpad,varchar(200),_tekeningfolder,varchar(200),revisie,integer,gebiedcode,varchar(3),tekeningnummer,varchar(50),fase,integer,datumUitzending,text,projectnaam,varchar(50),stedenbouwkundige,varchar(50),projectmanager,varchar(50),tekenaar,varchar(50),_klaar,varchar(200),SMP_Overzicht,revisie,integer,OBJECTID,integer,projectnaam,varchar(50),tekeningnummer,varchar(50),stedenbouwkundige,varchar(50),SHAPE_Length,float,SHAPE_Area,float,landschapsarchitect,varchar(50),tekenaar,varchar(50),fase,integer,actueel,integer,projectmanager,varchar(50),bestandsactualisatie,text,identificatie,text,programma,varchar(50),geplandeStartdatumBouw,text,datumOpmaak,text,datumUitzending,text,tekeningfolder,varchar(500),tekeningPDF,varchar(500),opmerking,varchar(50),bronMetadata,varchar(500),gebiedcode,varchar(3),gebiednaam,varchar(500)
    potGewijzigd -> AttributeRenamer
Note: actueel hernoemen naar actueel_org. / Als verderop blijkt dat dit kenmerk gewijzigd is / moet een UPDATE volgen. IN elk / ander geval moet deze feature worden genegeerd.
AttributeRenamer
    ATTR_TABLE = RENAME_SET_DEFAULT actueel > _actueel_org
    -> Actualiteitbepaler [In]
AttributeKeeper
    KEEP_ATTRS = identificatie
    -> FeatureMerger [SUPPLIER]
Note: backup
SMP_overzicht (writer GEODATABASE_FILE_3)
    attributes: OBJECTID integer, projectnaam char(50), tekeningnummer char(50), stedenbouwkundige char(50), SHAPE_Length double, SHAPE_Area double, landschapsarchitect char(50), tekenaar char(50), fase smallint, revisie smallint, actueel smallint, projectmanager char(50), bestandsactualisatie date, identificatie guid, programma char(50), geplandeStartdatumBouw date, datumOpmaak date, datumUitzending date, tekeningfolder char(500), tekeningPDF char(500), opmerking char(50), bronMetadata char(500), gebiedcode char(3), gebiednaam char(500)
Actualiteitbepaler
    GEBIEDCODE = @Value(gebiedcode)
    FASE = @Value(fase)
    _KLAAR = @Value(_klaar)
    TEKENINGNUMMER = @Value(tekeningnummer)
    REVISIE = @Value(revisie)
    Uit -> Tester_IdentificatieHasValue
    _Rejected_ -> Junction_10
Note: Heeft identificatie een waarde? / Zo ja: het is een bestaande feature --> UPDATE / als er daadwerkelijk iets is gewijzigd / zo nee: het is een nieuwe feature --> INSERT
Tester_IdentificatieHasValue
    TEST_DESCRIPTION = ""
    BOOL_OP = OR
    TEST_MODE = Automatic
    TEST_CLAUSE = TEST @Value(identificatie) ATTRIBUTE_HAS_VALUE ""
    PASSED -> Tester
    FAILED -> GUIDGenerator
Note: Is 'actueel' gewijzigd? / ja: UPDATE / nee: negeren / Er wordt vanuit gegaan / dat van bestaande features / alleen het kenmerk ' actueel' / kan wijzigen.
Tester
    TEST_DESCRIPTION = ""
    BOOL_OP = OR
    TEST_MODE = Automatic
    TEST_CLAUSE = TEST @Value(actueel) != @Value(_actueel_org)
    PASSED -> FeatureMerger [REQUESTOR]
Note: ophalen oorspronkelijkgeometrie. / Deze komen niet mee in de InlineQueriers. / Een alternatief is om daar / expliciet SELECT fme_feature_content / toe te passen, / maar dan komen alle kenmerken mee.
FeatureMerger
    PROCESS_DUPS = No
    JOIN_KEYS = @Value(identificatie) @Value(identificatie) AUTO
    SUPPLIERS_FIRST = No
    REJECT_NULL_MISSING_KEYS = No
    MERGE_TYPE = Geometry
    MERGED -> FeatureMerger_MERGED_-__AttributeCreator_UPD
    UNMERGED_REQUESTOR -> FeatureMerger_MERGED_-__AttributeCreator_UPD
    <REJECTED> -> Junction_16
FeatureMerger_MERGED_-__AttributeCreator_UPD: Junction
    -> AttributeCreator_UPD
Junction_16
    -> Junction_18
Note: huidige datum
DateTimeStamper
    INCLUDE_OFFSET = NO
    STAMP_TYPE = datetime
    TIMEZONE = local
    DATETIME_ATTR = bestandsactualisatie
    -> AttributeRemover
AttributeRemover
    REMOVE_ATTRS = _actueel_org,_klaar,_reader_error
    -> AttributeFilter_uitval
AttributeFilter_uitval
    ATTR_NAME = opmerking
    ATTR_VALUES = <Empty>,<Missing>,<Null>,<Unfiltered>,Bij deze uitzending is geen tekening gevonden.,Bij deze uitzending kon geen contour worden gevormd.
    <EMPTY> -> AttributeFilter__lt_EMPTY_gt__-__SMP_overzicht
    <MISSING> -> AttributeFilter__lt_EMPTY_gt__-__SMP_overzicht
    <NULL> -> AttributeFilter__lt_EMPTY_gt__-__SMP_overzicht
    <UNFILTERED> -> AttributeFilter__lt_EMPTY_gt__-__SMP_overzicht
    Bij deze uitzending is geen tekening gevonden. -> FaseRemapper [IN]
    Bij deze uitzending kon geen contour worden gevormd. -> FaseRemapper_2 [IN]
AttributeFilter__lt_EMPTY_gt__-__SMP_overzicht: Junction
    -> SMP_overzicht (writer GEODATABASE_FILE_2)
SMP_overzicht (writer GEODATABASE_FILE_2)
    attributes: projectnaam char(50), tekeningnummer char(50), stedenbouwkundige char(50), landschapsarchitect char(50), tekenaar char(50), fase smallint, revisie smallint, actueel smallint, projectmanager char(50), bestandsactualisatie date, identificatie guid, programma char(50), geplandeStartdatumBouw date, datumOpmaak date, datumUitzending date, tekeningfolder char(500), tekeningPDF char(500), opmerking char(50), bronMetadata char(500), gebiedcode char(3), gebiednaam char(500)
FaseRemapper
    FASE = @Value(fase)
    UIT -> uitzending_zonder_tekening (writer XLSXW_1)
uitzending_zonder_tekening (writer XLSXW_1)
    attributes: identificatie string(20), gebiedcode string(3), gebiednaam string(500), projectnaam string(50), tekeningnummer string(50), fase string(10), revisie number(20), datumUitzending datetime(20), projectmanager string(50), stedenbouwkundige string(50), tekenaar string(50), tekeningfolder string(500), bestandsactualisatie datetime(20), opmerking string(50)
FaseRemapper_2
    FASE = @Value(fase)
    UIT -> uitzending_zonder_contour (writer XLSXW_1)
uitzending_zonder_contour (writer XLSXW_1)
    attributes: identificatie string(20), gebiedcode string(3), gebiednaam string(500), projectnaam string(50), tekeningnummer string(50), fase string(10), revisie number(20), datumUitzending datetime(20), projectmanager string(50), stedenbouwkundige string(50), tekenaar string(50), tekeningfolder string(500), bestandsactualisatie datetime(20), opmerking string(50)
Junction_10
    -> Junction_12

Bookmark: per tekeningnr, fase, revisie ophalen van beschikbare pdf en dwg
AttributeKeeper_Path
    KEEP_ATTRS = path_rootname,path_directory_windows,path_extension,path_windows
    -> tekeningMetadaExtractor [In]
Note: Extraheert bij elke tekening: / gebiedscode, / tekeningnummer, / fase, / revisie / uit de naam van de / bovenliggende folderstructuur. / Als er geen revisie wordt gevonden dan / wordt revisie op 1 gezet.
tekeningMetadaExtractor
    _TEKENINGPAD = @Value(path_windows)
    Uit -> StringSearcherTek
    Uitval -> Junction
    _Rejected_ -> Junction_3
Note: Bevat bestandsnaam de / string 'tek'?
StringSearcherTek
    STRING_TO_SEARCH = @Value(path_rootname)
    CASE = no
    REGEXP = tek
    MATCHED -> StringSearcher_gevel_doorsnede
Note: Wegfilteren van bestanden / met 'doorsnede' of 'gevel' in de naam
StringSearcher_gevel_doorsnede
    STRING_TO_SEARCH = @Value(path_rootname)
    MATCHED_RESULT_ATTR = _first_match
    CASE = no
    REGEXP = doorsnede|gevel
    NOT_MATCHED -> StringSearcher_LVUZ
Junction
    -> Junction_2
Junction_3
    -> Junction_4

Bookmark: corrigeren fase bij LVUZ
  LVUZ zit in de nieuwe stijl in dezelfde map als VUZ.
  Als de bestandsnaam LVUZ bevat wordt de fase hieropaangepast.
StringSearcher_LVUZ
    STRING_TO_SEARCH = @Value(path_rootname)
    CASE = no
    REGEXP = LVUZ
    MATCHED -> AttributeCreator_LVUZ
    NOT_MATCHED -> StringSearcher_revisie
AttributeCreator_LVUZ
    ATTR_TABLE = SET_TO _fase = 3
    -> AttributeRemover_3

Bookmark: corrigeren revisie bij VUZ, GUZ, DUZ, WUZ
  Revisies hebben in principe in de nieuwe stijl een aparte map. Soms staan er echter revisies bij elkaar in 1 map.
  Als de bestandsnaam een revisienummer bevat dan wordt hier de revisie daarop aangepast.
StringSearcher_revisie
    STRING_TO_SEARCH = @Value(path_rootname)
    CASE = no
    MATCHED_PARTS_ATTR = _subexp
    REGEXP = [VGDW]UZ\s?(\d)
    MATCHED -> ListIndexer
    NOT_MATCHED -> StringSearcher_revisie_NOT_MATCHED_-__AttributeKeeper
ListIndexer
    INDEX = 0
    LIST_ATTR = _subexp{}
    -> AttributeCreator_revisie
    <REJECTED> -> Junction_5
AttributeCreator_revisie
    ATTR_TABLE = SET_TO _revisie = @Value(part)
    -> StringSearcher_revisie_NOT_MATCHED_-__AttributeKeeper
Junction_5

Bookmark: corrigeren fase en revisie
StringSearcher_revisie_NOT_MATCHED_-__AttributeKeeper: Junction
    -> AttributeRemover_3
AttributeRemover_3
    REMOVE_ATTRS = path_rootname,startIndex,part
    LIST_ATTRS = _subexp{}
    -> StringCaseChanger_Path_extension

Bookmark: uitsplitsen pdf / dwg en verwijderen dubbele tekeningen
StringCaseChanger_Path_extension
    ATTRCHOICE = Selected Attributes
    ATTRLIST = path_extension
    CHANGE_TYPE = lowercase
    -> AttributeFilter_Path_extension
AttributeFilter_Path_extension
    ATTR_NAME = path_extension
    ATTR_VALUES = <Empty>,<Missing>,<Null>,<Unfiltered>,dwg,pdf
    dwg -> AttributeManager_Path_dwg
    pdf -> AttributeManager_Path_pdf
AttributeManager_Path_dwg
    ATTR_TABLE:
      RENAME_SET_VALUE path_directory_windows > _tekeningfolder
      RENAME_SET_VALUE path_windows > _tekeningpad
      REMOVE path_extension
    -> DuplicateFilter_dwg
DuplicateFilter_dwg
    INPUT_ORDERED_CHOICE = No
    KEYATTR = _fase _revisie _gebiedcode _tekeningnummer
    UNIQUE -> FeatureMerger_2 [REQUESTOR]
AttributeManager_Path_pdf
    ATTR_TABLE:
      REMOVE path_directory_windows
      RENAME_SET_VALUE path_windows > _tekeningPDF
      REMOVE path_extension
    -> DuplicateFilter_pdf
DuplicateFilter_pdf
    INPUT_ORDERED_CHOICE = No
    KEYATTR = _fase _revisie _gebiedcode _tekeningnummer
    UNIQUE -> FeatureMerger_2 [SUPPLIER]
Note: Left outer join pdf - dwg
FeatureMerger_2
    PROCESS_DUPS = No
    JOIN_KEYS = @Value(_gebiedcode) @Value(_gebiedcode) AUTO @Value(_tekeningnummer) @Value(_tekeningnummer) AUTO @Value(_fase) @Value(_fase) AUTO @Value(_revisie) @Value(_revisie) AUTO
    SUPPLIERS_FIRST = No
    REJECT_NULL_MISSING_KEYS = No
    ATTR_CONFLICT_RES = Use Requestor
    MERGE_TYPE = Attributes Only
    ATTR_ACCUM_MODE = Merge Supplier
    IGNORE_NULLS = No
    MERGED -> FeatureMerger_UNUSED_SUPPLIER_-__FeatureMerger_UnusedSupplier
    UNMERGED_REQUESTOR -> FeatureMerger_UNUSED_SUPPLIER_-__FeatureMerger_UnusedSupplier
    UNUSED_SUPPLIER -> FeatureMerger_UNUSED_SUPPLIER_-__FeatureMerger_UnusedSupplier
    <REJECTED> -> Junction_6
FeatureMerger_UNUSED_SUPPLIER_-__FeatureMerger_UnusedSupplier: Junction
    -> StringPairReplacer_3
Note: in tekeningnummer '-' vervangen / door '/' / bijv. 18-00046 wordt 18/00046
StringPairReplacer_3
    MAP = - /
    RESULT_ATTR = _tekeningnummer
    SRC_ATTR = _tekeningnummer
    CASE = no
    -> StringPairReplacer_2_OUTPUT_-__FeatureMerger_UitzendingMetTekening_REQUESTOR
Junction_6

Bookmark: uitval
Junction_2
    -> Logger
Logger
    MAXCOORDS = 20
    MAXFEATS = 20
    MESSAGE = Feature is:
Junction_4
    -> _Rejected_
Junction_14
    -> _Rejected_
Junction_8
    -> _Rejected_
Junction_18
    -> _Rejected_
Junction_12
    -> _Rejected_
Junction_20
    -> _Rejected_
_Rejected_: Logger
    MAXCOORDS = 20
    MAXFEATS = 20
    MESSAGE = Feature is:

Bookmark: Inlezen uitzendlijst in CSV-formaat
  Versie 2017.1 geeft soms een foutmelding bij het inlezen van een excel-bestand (in xlsx-indeling).
  De volgende foutmelding treedt dan op:
  Excel Reader: Could not open file 'K:\SO\RW\Algemeen\UITZENDINGEN NIEUWE STIJL\2 SMP\001 Sjablonen\Schema Voortgang SMP def.xlsx', file is too large. Try switching to 64-bit FME, or exporting the Excel file to CSV. (...)
  De workaround is: 
  1. kopieer het excelbestand naar een csv-bestand 
      (K:\GEODATA\Kennisloods\Beheer\Uitzendingen_overzicht\Schema Voortgang SMP def.csv)
  2. schakel de excel-reader uit 
       ('Schema Voortgang SMP def [XLSXR]')
  3. schakel de csv-reader in 
      ('Schema Voortgang SMP def [CSV2]')
  4. voer het script uit
Note: kopie uitzendlijst in CSV-formaat
Schema Voortgang SMP def (reader CSV2_1)
    attributes: col0 string, col1 string, col2 string, col3 string, col4 string, col5 string, col6 string, col7 string, col8 string, col9 string, col10 string, col11 string, col12 string, col13 string, col14 string, col15 string, col16 string, col17 string, col18 string, col19 string, col20 string, col21 string, col22 string, col23 string, col24 string, col25 string, col26 string, col27 string, col28 string, col29 string
    -> Tester_tekeningnummerHasValueCSV
Note: wegfilteren lege rijen / en / rijen die niet met de volgende reguliere / expressie beginnen: ^\d{2}-\d{5}$
Tester_tekeningnummerHasValueCSV
    TEST_DESCRIPTION = ""
    BOOL_OP = AND
    TEST_MODE = Automatic
    TEST_CLAUSE:
      TEST @Value(col0) ATTRIBUTE_HAS_VALUE ""
      TEST @Value(col0) CONTAINS_REGEX ^\d{2}-\d{5}$
    PASSED -> AttributeManager_Uitzendlijst_2
    PASSED -> StatisticsCalculator_CSV
AttributeManager_Uitzendlijst_2
    ATTR_TABLE:
      RENAME_SET_VALUE col0 > _tekeningnummer
      RENAME_SET_VALUE col1 > _gebiedcode
      RENAME_SET_VALUE col2 > _projectnaam
      RENAME_SET_VALUE col3 > _stedenbouwkundige
      RENAME_SET_VALUE col4 > _tekenaar
      RENAME_SET_VALUE col5 > _projectmanager
      RENAME_SET_VALUE col6 > Verzenddatum_VUZ
      REMOVE col7
      REMOVE col8
      RENAME_SET_VALUE col9 > Verzenddatum_GUZ
      REMOVE col10
      REMOVE col11
      RENAME_SET_VALUE col12 > Verzenddatum_DUZ
      REMOVE col13
      REMOVE col14
      RENAME_SET_VALUE col15 > Verzenddatum_WUZ
      REMOVE col16
      RENAME_SET_VALUE col17 > _klaar
      REMOVE col18
      REMOVE col19
      REMOVE col20
      REMOVE col21
      REMOVE col22
      REMOVE col23
      REMOVE col24
      REMOVE col25
      REMOVE col26
      REMOVE col27
      REMOVE col28
      REMOVE col29
      REMOVE fme_feature_type
    -> NullAttributeMapper
NullAttributeMapper
    ATTRCHOICE = Selected Attributes
    NULL_TREATMENT = Null
    SOURCE_ATTR_VAL = Empty "Missing (Selected Attributes Only)"
    ATTRLIST = _klaar Verzenddatum_WUZ _gebiedcode _projectnaam _tekenaar Verzenddatum_GUZ _tekeningnummer _stedenbouwkundige Verzenddatum_DUZ Verzenddatum_VUZ _projectmanager
    -> StringPairReplacer

Bookmark: testen of de uitzenindingen niet tegelijk in CSV-formaat en in Excel-formaat worden ingelezen.
StatisticsCalculator_CSV
    PREPEND_ATTR_NAME_CHOICE = For multiple results only
    STATS_ATTRS = fme_feature_type
    COMPUTE_HISTOGRAM = NO
    COUNT_ATTR = _countCSV
    SUMMARY -> Tester_aantalUItzendingen
StatisticsCalculator_XLSX
    PREPEND_ATTR_NAME_CHOICE = For multiple results only
    STATS_ATTRS = fme_feature_type
    COMPUTE_HISTOGRAM = NO
    COUNT_ATTR = _countXLSX
    SUMMARY -> Tester_aantalUItzendingen
Note: Het script wordt afgebroken / als de uitzendingen zowel in / CSV-formaat als in Excel-formaat / worden ingelezen.
Tester_aantalUItzendingen
    TEST_DESCRIPTION = ""
    BOOL_OP = OR
    TEST_MODE = Automatic
    TEST_CLAUSE:
      TEST @Value(_countXLSX) = @Evaluate(@Value(_countCSV)+@Value(_countXLSX))
      TEST @Value(_countCSV) = @Evaluate(@Value(_countCSV)+@Value(_countXLSX))
    FAILED -> Terminator_2
Terminator_2
    MESSAGE = De uitzendingenlijst wordt zowel in CSV- als in Excelformaat ingelezen. Schakel een van beide uit.

Bookmark: inlezen uitzendlijst in Excel-formaat
Note: onduidelijk is nog hoe met revisies wordt / omgegeaan.
Note: inlezen uitzendingenlijst: / Schema Voortgang SMP def.xls / tabblad: Opgave
Opgave (reader XLSXR_1)
    attributes: IP- of tekeningnr char(9), Gebied char(3), Locatie char(28), Ontwerper char(21), Tekenaar char(13), Gebiedscoordinator/-commissie _of bestuurlijk char(11), Verzenddatum_VUZ date, vervaldatum_VUZ _(28 wrkdgn) date, VUZ number(2,0), Verzenddatum_GUZ string, vervaldatum_GUZ _(5 wrkdgn) date, GUZ number(2,0), Verzenddatum_DUZ string, vervaldatum_DUZ _(28 wrkdgn) date, DUZ number(2,0), Verzenddatum_WUZ string, WUZ number(2,0), Klaar? J/N string, Doorlooptijd in dagen tot vandaag number(6,0), Opmerkingen bij deze IP: string, U string, V string, W string, VANDAAG date, AANTAL WERKDAGEN number(3,0), AANTAL WERKDAGEN00 number(3,0), AANTAL WERKDAGEN01 number(2,0), AB string, AC string, AD string,
      AE string
    -> Tester_tekeningnummerHasValue
Note: wegfilteren lege / rijen
Tester_tekeningnummerHasValue
    TEST_DESCRIPTION = ""
    BOOL_OP = OR
    TEST_MODE = Automatic
    TEST_CLAUSE = TEST @Value(IP- of tekeningnr) ATTRIBUTE_HAS_VALUE ""
    PASSED -> AttributeManager_Uitzendlijst
    PASSED -> StatisticsCalculator_XLSX
AttributeManager_Uitzendlijst
    ATTR_TABLE:
      RENAME_SET_VALUE IP- of tekeningnr > _tekeningnummer
      RENAME_SET_VALUE Gebied > _gebiedcode
      RENAME_SET_VALUE Locatie > _projectnaam
      RENAME_SET_VALUE Ontwerper > _stedenbouwkundige
      RENAME_SET_VALUE Tekenaar > _tekenaar
      RENAME_SET_VALUE Gebiedscoordinator/-commissie _of bestuurlijk > _projectmanager
      REMOVE vervaldatum_VUZ _(28 wrkdgn)
      REMOVE VUZ
      REMOVE vervaldatum_GUZ _(5 wrkdgn)
      REMOVE GUZ
      REMOVE vervaldatum_DUZ _(28 wrkdgn)
      REMOVE DUZ
      REMOVE WUZ
      RENAME_SET_VALUE Klaar? J/N > _klaar
      REMOVE Doorlooptijd in dagen tot vandaag
      REMOVE Opmerkingen bij deze IP:
      REMOVE U
      REMOVE V
      REMOVE W
      REMOVE VANDAAG
      REMOVE AANTAL WERKDAGEN
      REMOVE AANTAL WERKDAGEN00
      REMOVE AANTAL WERKDAGEN01
      REMOVE AB
      REMOVE AC
      REMOVE AD
      REMOVE AE
      REMOVE fme_feature_type
    -> StringPairReplacer

Bookmark: bepalen fase + datumuitzending
StringPairReplacer_OUTPUT_-__Tester_VerzenddatumVUZHasValue: Junction
    -> Tester_VerzenddatumVUZHasValue
    -> Tester_VerzenddatumGUZHasValue
    -> Tester_VerzenddatumDUZHasValue
    -> Tester_VerzenddatumWUZHasValue
Tester_VerzenddatumVUZHasValue
    TEST_DESCRIPTION = ""
    BOOL_OP = OR
    TEST_MODE = Automatic
    TEST_CLAUSE = TEST @Value(Verzenddatum_VUZ) ATTRIBUTE_HAS_VALUE ""
    PASSED -> AttributeManager_VUZ
AttributeManager_VUZ
    ATTR_TABLE:
      RENAME_SET_VALUE Verzenddatum_VUZ > _datumUitzending
      REMOVE Verzenddatum_GUZ
      REMOVE Verzenddatum_DUZ
      REMOVE Verzenddatum_WUZ
      SET_TO _fase = 2
    -> AttributeManager_VUZ_OUTPUT
Tester_VerzenddatumGUZHasValue
    TEST_DESCRIPTION = ""
    BOOL_OP = OR
    TEST_MODE = Automatic
    TEST_CLAUSE = TEST @Value(Verzenddatum_GUZ) ATTRIBUTE_HAS_VALUE ""
    PASSED -> AttributeManager_GUZ
AttributeManager_GUZ
    ATTR_TABLE:
      REMOVE Verzenddatum_VUZ
      RENAME_SET_VALUE Verzenddatum_GUZ > _datumUitzending
      REMOVE Verzenddatum_DUZ
      REMOVE Verzenddatum_WUZ
      SET_TO _fase = 4
    -> AttributeManager_VUZ_OUTPUT
Tester_VerzenddatumDUZHasValue
    TEST_DESCRIPTION = ""
    BOOL_OP = OR
    TEST_MODE = Automatic
    TEST_CLAUSE = TEST @Value(Verzenddatum_DUZ) ATTRIBUTE_HAS_VALUE ""
    PASSED -> AttributeManager_DUZ
AttributeManager_DUZ
    ATTR_TABLE:
      REMOVE Verzenddatum_VUZ
      REMOVE Verzenddatum_GUZ
      RENAME_SET_VALUE Verzenddatum_DUZ > _datumUitzending
      REMOVE Verzenddatum_WUZ
      SET_TO _fase = 5
    -> AttributeManager_VUZ_OUTPUT
Tester_VerzenddatumWUZHasValue
    TEST_DESCRIPTION = ""
    BOOL_OP = OR
    TEST_MODE = Automatic
    TEST_CLAUSE = TEST @Value(Verzenddatum_WUZ) ATTRIBUTE_HAS_VALUE ""
    PASSED -> AttributeManager_WUZ
AttributeManager_WUZ
    ATTR_TABLE:
      REMOVE Verzenddatum_VUZ
      REMOVE Verzenddatum_GUZ
      REMOVE Verzenddatum_DUZ
      RENAME_SET_VALUE Verzenddatum_WUZ > _datumUitzending
      SET_TO _fase = 6
    -> AttributeManager_VUZ_OUTPUT
AttributeManager_VUZ_OUTPUT: Junction
    -> InlineQuerierTekening [Uitzendingenlijst]

Bookmark: revisie op 1 zetten als revisie geen waarde heeft
Tester_revisie_hasValue
    TEST_DESCRIPTION = ""
    BOOL_OP = OR
    TEST_MODE = Automatic
    TEST_CLAUSE = TEST @Value(revisie) ATTRIBUTE_HAS_VALUE ""
    PASSED -> AttributeCreator_Revisie1_OUTPUT_-__SMP_overzicht
    FAILED -> AttributeCreator_Revisie1
AttributeCreator_Revisie1
    ATTR_TABLE = SET_TO revisie = 1
    -> AttributeCreator_Revisie1_OUTPUT_-__SMP_overzicht
AttributeCreator_Revisie1_OUTPUT_-__SMP_overzicht: Junction
    -> InlineQuerierTekening [SMP_overzicht]
    -> InlineQuerierPotentieelGewijzigd [SMP_Overzicht]
    -> AttributeKeeper

Bookmark: tekeningpaden verwerken tot contouren
FeatureMerger_UitzendingMetTekening
    PROCESS_DUPS = No
    JOIN_KEYS = @Value(_gebiedcode) @Value(gebiedcode) AUTO @Value(_tekeningnummer) @Value(tekeningnummer) AUTO @Value(_fase) @Value(fase) AUTO
    SUPPLIERS_FIRST = No
    REJECT_NULL_MISSING_KEYS = No
    ATTR_CONFLICT_RES = Use Requestor
    MERGE_TYPE = Attributes Only
    ATTR_ACCUM_MODE = Merge Supplier
    IGNORE_NULLS = No
    MERGED -> FeatureReader [INITIATOR]
    UNUSED_SUPPLIER -> AttributeCreator_uitzendingZonderTekening
    <REJECTED> -> Junction_13
Note: Ophalen autocad-lagen / aan de hand van de tekeningpaden. / Alleen de lagen / X-XX-AL-PROJECTGRENS-G / X-XX-AL-PROJECTGRENS_SMP-G / X-XX-AL-WIJZIGINGSGRENS-G / worden omgezet naar een contour.
FeatureReader
    FORMAT = ACAD
    ACAD_EVALUATE_MLINE_GEOM = no
    ACAD_VISIBLE_ATTRIBUTES_AS_TEXT = yes
    ACAD_RESOLVE_BLOCKS = yes
    ACAD_PRESERVE_INSERTS = no
    ACAD_IGNORE_FROZEN_LAYERS = no
    ACAD_INTERPRET_EXTENDED_DATA = yes
    ACAD_PRESERVE_COMPLEX_HATCHES = no
    ACAD_CONVERT_ZERO_LENGTH_ARCS_TO_POINTS = yes
    ACAD_STORE_SPLINE_DEFS = yes
    ACAD_STORE_LAYER_INFO = no
    ACAD_OUTPUT_ZERO_LENGTH_LINES_AS_LINES = no
    COMBINE_GEOM = Use Result
    ACAD_EXPLODE_MTEXT = yes
    ACAD_READ_SYS_VARS = no
    ACAD_IGNORE_UCS = no
    ACAD_READ_PAPER_SPACE = NO
    ACAD_QUERY_FEATURE_TYPES_FOR_MERGE_FILTERS = Yes
    ACAD_STORE_INSERT_POINT = no
    ACAD_RESOLVE_DIMENSIONS = yes
    ACAD_STRUCTURE_EXTENDED_DATA = no
    ACAD_READ_AS_2_5D = no
    ACAD_USE_BLOCK_LAYER_INFO = no
    COORDSYS = EPSG:28992
    FEATURETYPES = X-XX-AL-PROJECTGRENS-G X-XX-AL-WIJZIGINGSGRENS-G X-XX-AL-PROJECTGRENS_SMP-G
    ACAD_METAFILE = acad
    ACAD_ALL_MERGED_FILTERS_NEED_NO_DEFS = Yes
    ACAD_USE_BLOCK_HEADER_LAYER = yes
    ACAD_READ_USER_DICTIONARIES = no
    ACAD_READ_GROUPS = no
    OUTPUT_FEATURES_DISPLAY = Data Features
    ACAD_READ_MODEL_SPACE = yes
    ACAD_XRECORD_READING = None
    ACAD_READ_PROXY_GRAPHICS = yes
    INTERACT = <No Spatial Filter>
    ACAD_LIST_ATTRIBUTE_ENTITY_DATA = yes
    ACAD_USE_SEARCH_ENVELOPE = NO
    ACAD_RESOLVE_ENTITY_COLOR = yes
    ATTR_ACCUM_MODE = Only Use Result
    DATASET = @Value(_tekeningpad)
    ACAD_STORE_BULGE_INFO = no
    ACAD_APPLY_WORLD_FILE = yes
    ACAD_LIST_EXTENDED_DATA = yes
    ATTRS_TO_EXPOSE = "autocad_source_filename "
    ACAD_READ_XREFS = no
    ACAD_PRESERVE_CLIPPED_RASTERS = no
    <OTHER> -> ContourReconstructor [AutoCadFeatures]
    INITIATOR -> ContourReconstructor [Initiator]
    <REJECTED> -> AttributeCreator_uitzendingZonderTekening
AttributeCreator_uitzendingZonderTekening
    ATTR_TABLE = SET_TO _opmerking = Bij deze uitzending is geen tekening gevonden.
    -> AttributeManager_NieuwContour
Junction_13
    -> Junction_14
Note: TIR
Gemeente_vlakken (reader ESRISHAPE_1)
    attributes: GROEP char(9), KLASSE char(30), DGDT_ID long, CODE long, HERKOMST char(20), STATUS char(25), NIVO long, INWIN char(10), GEMEENTE long, GEBIED long, BUURT long, SUBBUURT long, SBTDEEL long, BLOK long, TEKST char(80), GEBDNAAM char(254), BUURTNAAM char(254), LAAG char(20)
    -> ContourReconstructor [Gemeente]
Note: Maakt plancontouren aan aan de hand van aangeleverde plangrenzen. / clippen binnen gemeentegrens / stroken van arcs / snappen van edges en vertices binnen 5 meter / vormen van polygonen uit lines, arcs en ellipses / verwijderen binnengrenzen / verwijderen polygonen zonder oppervlakte / aggregeren naar oorspronkelijk bestandsnaam + -pad / ophalen projectmetadata + bepalen van uitval
ContourReconstructor
    _FASE = @Value(_fase)
    _GEBIEDCODE = @Value(_gebiedcode)
    _TEKENINGNUMMER = @Value(_tekeningnummer)
    _MATCHED_RECORDS = @Value(_matched_records)
    _TEKENINGPAD = @Value(_tekeningpad)
    AUTOCAD_SOURCE_FILENAME = @Value(autocad_source_filename)
    _REVISIE = @Value(_revisie)
    Uit -> AttributeManager_NieuwContour
    _Rejected_ -> Junction_7
Junction_7
    -> Junction_8
AttributeManager_NieuwContour
    ATTR_TABLE:
      RENAME_SET_VALUE _opmerking > opmerking
      REMOVE _tekeningnummer
      REMOVE _gebiedcode
      REMOVE _fase
      RENAME_SET_VALUE _tekeningpad > tekeningPDF
      RENAME_SET_VALUE _revisie > revisie
      RENAME_SET_VALUE _tekeningfolder > tekeningfolder
    -> TestFilter

Bookmark: voorbereiden metadata voor nieuwe features
  Er wordt hier rekening gehouden met verschillende datumnotaties.
TestFilter
    DEFAULT_VALUE = <UNFILTERED>
    TEST_LIST = BOOL_OP,OR,COMPOSITE_TEST,<Unused>,TEST_CLAUSE,"TEST @Value(datumUitzending) CONTAINS_REGEX ^\d{8}$",^\d{8}$,BOOL_OP,OR,COMPOSITE_TEST,<Unused>,TEST_CLAUSE,"TEST @Value(datumUitzending) CONTAINS_REGEX ^\d-\d{1,2}-\d{4}$",^\d-\d{1,2}-\d{4}$,BOOL_OP,OR,COMPOSITE_TEST,<Unused>,TEST_CLAUSE,"TEST @Value(datumUitzending) CONTAINS_REGEX ^\d{2}-\d{1,2}-\d{4}$",^\d{2}-\d{1,2}-\d{4}$
    <UNFILTERED> -> Terminator
    ^\d{8}$ -> DateTimeConverter_Ymd
    ^\d-\d{1,2}-\d{4}$ -> DateTimeConverter_eNY
    ^\d{2}-\d{1,2}-\d{4}$ -> DateTimeConverter_dNY
DateTimeConverter_Ymd
    IN_FORMAT = %Y%m%d$
    OUT_FORMAT = FME
    REPAIR_INPUT = NO
    DATETIME_ATTR = datumUitzending
    -> DateTimeConverter_dNY_OUTPUT_-__AttributeValueMapper
    <REJECTED> -> Junction_19
DateTimeConverter_eNY
    IN_FORMAT = %e-%N-%Y
    OUT_FORMAT = FME
    REPAIR_INPUT = NO
    DATETIME_ATTR = datumUitzending
    -> DateTimeConverter_dNY_OUTPUT_-__AttributeValueMapper
    <REJECTED> -> Junction_19
DateTimeConverter_dNY
    IN_FORMAT = %d-%N-%Y
    OUT_FORMAT = FME
    REPAIR_INPUT = NO
    DATETIME_ATTR = datumUitzending
    -> DateTimeConverter_dNY_OUTPUT_-__AttributeValueMapper
    <REJECTED> -> Junction_19
DateTimeConverter_dNY_OUTPUT_-__AttributeValueMapper: Junction
    -> AttributeValueMapper
Note: gebiednaam
AttributeValueMapper
    VAL_ATTR = gebiednaam
    LUT = CE,Centrum,CH,Charlois,DE,Delfshaven,FE,Feijenoord,HH,Hoek van Holland,HO,Hoogvliet,HS,Hillegersberg-Schiebroek,IJS,IJsselmonde,YS,IJsselmonde,KC,Kralingen-Crooswijk,NO,Noord,OV,Overschie,PA,Prins Alexander-Nesselande,PE,Pernis,RO,Rozenburg
    DIRECTION = Forward (Source To Destination)
    SRC = gebiedcode
    -> Actualiteitbepaler [In]
Junction_19
    -> Junction_20
Terminator
    MESSAGE = datumUItzending heeft een afwijkend formaat

Bookmark: voorbereiding database UPDATE
Note: fme_db_operation := UPDATE
AttributeCreator_UPD
    ATTR_TABLE = SET_TO fme_db_operation = UPDATE
    -> AttributeRemover_2
AttributeRemover_2
    REMOVE_ATTRS = bestandsactualisatie
    -> DateTimeStamper

Bookmark: voorbereiding database INSERT
Note: aanmaken uniek id
GUIDGenerator
    -> AttributeRenamer_identficatie
AttributeRenamer_identficatie
    ATTR_TABLE = RENAME_SET_DEFAULT GFID > identificatie
    -> AttributeCreator_INS
Note: fme_db_operation := INSERT
AttributeCreator_INS
    ATTR_TABLE = SET_TO fme_db_operation = INSERT
    -> DateTimeStamper

FME custom transformer Actualiteitbepaler
Bepaalt of de feature de laatst voorkomende fase + revisie is.
Deze krijgt actualiteit =1, alle andere features krijgen actualiteit =0.
Features die in de uitzendlijst als afgerond zijn aangemerkt worden altijd op 0 gezet.

Parameters:
- GEBIEDCODE = @Value(gebiedcode)   # gebiedcode
- REVISIE = @Value(revisie)   # revisie
- _KLAAR = @Value(_klaar)   # Klaar
- FASE = @Value(fase)   # fase
- TEKENINGNUMMER = @Value(tekeningnummer)   # tekeningnummer

In (input)
    -> Tester_klaarHasValue
_Rejected_ (output)

Bookmark: bepalen van actualiteit
Note: Als '_klaar' niet leeg is / dan is de actualiteit altijd 0
Tester_klaarHasValue
    TEST_DESCRIPTION = ""
    BOOL_OP = OR
    TEST_MODE = Automatic
    TEST_CLAUSE = TEST @Value(_klaar) ATTRIBUTE_HAS_VALUE ""
    PASSED -> AttributeCreator_actueel_0_klaar
    FAILED -> FeatureMerger [REQUESTOR]
    FAILED -> AttributeKeeper
AttributeCreator_actueel_0_klaar
    ATTR_TABLE = SET_TO actueel = 0
    -> AttributeCreator_actueel_0_klaar_OUTPUT_-__Tester_IdentificatieHasValue
Note: Attributes to Keep: / gebiedcode, / revisie, / fase, / tekeningnummer
AttributeKeeper
    KEEP_ATTRS = gebiedcode,revisie,fase,tekeningnummer
    -> DuplicateFilter
DuplicateFilter
    INPUT_ORDERED_CHOICE = No
    KEYATTR = gebiedcode tekeningnummer fase revisie
    UNIQUE -> AttributeCopier
Note: per tekeningnummer / een lijst maken met / fase en revisie
ListBuilder
    LIST_ATTRS_TO_INCLUDE = fase revisie _faserevisie
    GROUP_BY = gebiedcode tekeningnummer
    GROUPS_ORDERED = No
    LIST_NAME = _list
    -> ListElementCounter
ListElementCounter
    CNT_ATTR = _element_count
    LIST_NAME = _list{}
    -> Tester_1_fase_revisie
Note: als er maar 1 combi / fase/revisie is dan is / die tekening per definitie / actueel
Tester_1_fase_revisie
    TEST_DESCRIPTION = ""
    BOOL_OP = OR
    TEST_MODE = Automatic
    TEST_CLAUSE = TEST @Value(_element_count) <= 1
    PASSED -> ListExploder
    FAILED -> ListSorter
Note: sorteren op fase+revisie; / de hoogste waarde / (de actuele versie) komt / heeft index 0.
ListSorter
    SRC_LIST = _list{}._faserevisie
    TYPE = Alphabetic
    ORDER = Descending
    -> ListExploder
ListExploder
    ATTR_ACCUM_MODE = Merge List Attributes
    ATTR_CONFLICT_RES = Use List Attribute Values
    LIST_ATTR = _list{}
    INDEX_ATTR = _element_index
    ELEMENTS -> Tester_3
    <REJECTED> -> FeatureMerger__REJECTED__-__Rejected
Note: list index = 0?
Tester_3
    TEST_DESCRIPTION = ""
    BOOL_OP = OR
    TEST_MODE = Automatic
    TEST_CLAUSE = TEST @Value(_element_index) = 0
    PASSED -> AttributeCreator_actueel_1
    FAILED -> AttributeCreator_actueel_0
AttributeCreator_actueel_1
    ATTR_TABLE = SET_TO actueel = 1
    -> AttributeKeeper_2
AttributeCreator_actueel_0
    ATTR_TABLE = SET_TO actueel = 0
    -> AttributeKeeper_2
AttributeKeeper_2
    KEEP_ATTRS = gebiedcode,revisie,actueel,fase,tekeningnummer
    -> FeatureMerger [SUPPLIER]
FeatureMerger
    PROCESS_DUPS = No
    JOIN_KEYS = @Value(tekeningnummer) @Value(tekeningnummer) AUTO @Value(fase) @Value(fase) AUTO @Value(revisie) @Value(revisie) AUTO @Value(gebiedcode) @Value(gebiedcode) AUTO
    SUPPLIERS_FIRST = No
    REJECT_NULL_MISSING_KEYS = No
    ATTR_CONFLICT_RES = Use Requestor
    MERGE_TYPE = Attributes Only
    ATTR_ACCUM_MODE = Merge Supplier
    IGNORE_NULLS = No
    MERGED -> AttributeCreator_actueel_0_klaar_OUTPUT_-__Tester_IdentificatieHasValue
    <REJECTED> -> FeatureMerger__REJECTED__-__Rejected
AttributeCreator_actueel_0_klaar_OUTPUT_-__Tester_IdentificatieHasValue: Junction
    -> Uit (output)
Uit (output)
FeatureMerger__REJECTED__-__Rejected: Junction
    -> _Rejected_ (output)

Bookmark: aanmaken sorteerkenmerk
  We willen sorteren op fase, revisie. De ListSorter kan echter maar op 1 veld sorteren. 
  Daarom wordt hier fase en revisie gecombineerd tot "<fase>.<revisie>"; waarbij NULL-waardes als 0 worden beschouwd
AttributeCopier
    ATTR_TABLE:
      COPY fase > _fase
      COPY revisie > _revisie
    -> NullAttributeMapper
NullAttributeMapper
    NEW_VALUE = 0
    ATTRCHOICE = Selected Attributes
    NULL_TREATMENT = New Value
    SOURCE_ATTR_VAL = Null Empty "Missing (Selected Attributes Only)"
    ATTRLIST = _revisie _fase
    -> StringConcatenator
StringConcatenator
    VAL_ATTR = _faserevisie
    PARM_LINE = @Value(_fase).@Value(_revisie)
    ACTION = Create New Attribute
    -> ListBuilder

FME custom transformer FaseRemapper
Converteert de fase van integer naar een omschrijving:
1 -->  concept
2 --> VUZ (voorlopige uitzending)
3 -->  LVUZ (laatste voorlopige uitzending)
4 --> GUZ (goedkeuringsuitzending)
5 --> DUZ (definitieve uitzending)
6 --> WUZ (wijzigingsuitzending)

Parameters:
- FASE = @Value(fase)   # fase

IN (input)
    -> AttributeValueMapper_Fase_int_naar_char
AttributeValueMapper_Fase_int_naar_char
    VAL_ATTR = fase
    LUT = 1,concept,2,VUZ,3,LVUZ,4,GUZ,5,DUZ,6,WUZ
    DIRECTION = Forward (Source To Destination)
    SRC = fase
    -> UIT (output)
UIT (output)

FME custom transformer tekeningMetadaExtractor
Extraheert bij elke tekening de gebiedscode, tekeningnummer, fase en revisie uit de naam van de bovenliggende folderstructuur.

Parameters:
- _TEKENINGPAD = @Value(_tekeningpad)   # Tekeningpad

In (input)
    -> AttributeSplitter
AttributeSplitter
    DROP_EMPTY_PARTS = No
    TRIM_OPTION = Both
    ATTR_NAME = _tekeningpad
    DELIMITER = \
    LIST_NAME = _directory
    -> ListIndexer_gebied
AttributeManager
    ATTR_TABLE:
      REMOVE _directory{}
      REMOVE gebied_directory
      REMOVE tekeningnummer_directory
      REMOVE _tekeningnrMatches{}.part
      REMOVE _tekeningnrMatches{}.startIndex
      RENAME_SET_VALUE tekeningnrpart > _tekeningnummer
      REMOVE tekeningnrstartIndex
      REMOVE _tekeningpad
      REMOVE fase_directory
      REMOVE revisie_directory
      REMOVE fasesubexpressies{}.part
      REMOVE fasesubexpressies{}.startIndex
      REMOVE fasepart
      REMOVE fasestartIndex
    -> Uit (output)
Uit (output)

Bookmark: bepalen gebiedcode
ListIndexer_gebied
    INDEX = 6
    PREFIX = gebied
    LIST_ATTR = _directory{}
    -> StringSearcher_gebied
    <REJECTED> -> Junction_9
StringSearcher_gebied
    STRING_TO_SEARCH = @Value(gebied_directory)
    MATCHED_RESULT_ATTR = _gebiedcode
    CASE = no
    REGEXP = ^(\w{2,3})
    MATCHED -> AttributeValueMapper
    NOT_MATCHED -> AttributeCreator_geenGebied
Note: IJS wordt YS
AttributeValueMapper
    VAL_ATTR = _gebiedcode
    DEFAULT_VALUE = @Value(_gebiedcode)
    LUT = IJS,YS
    DIRECTION = Forward (Source To Destination)
    SRC = _gebiedcode
    -> ListIndexer_tekeningnummer
AttributeCreator_geenGebied
    ATTR_TABLE = SET_TO uitvalreden = Tekening heeft geen gebiedcode.
    -> Junction
Junction
    -> Junction_2
Junction_9
    -> Junction_10

Bookmark: bepalen tekeningnummer
ListIndexer_tekeningnummer
    INDEX = 7
    PREFIX = tekeningnummer
    LIST_ATTR = _directory{}
    -> StringSearcher_tekeningnummer
    <REJECTED> -> Junction_5
StringSearcher_tekeningnummer
    STRING_TO_SEARCH = @Value(tekeningnummer_directory)
    CASE = no
    MATCHED_PARTS_ATTR = _tekeningnrMatches
    REGEXP = ^SMP\s?(\d{2}-\d{4,8})
    MATCHED -> ListIndexer
    NOT_MATCHED -> AttributeCreator_geenTekeningnummmer
ListIndexer
    INDEX = 0
    PREFIX = tekeningnr
    LIST_ATTR = _tekeningnrMatches{}
    -> ListIndexer_fase_2
    <REJECTED> -> Junction_11
Junction_11
    -> Junction_12
AttributeCreator_geenTekeningnummmer
    ATTR_TABLE = SET_TO uitvalreden = Tekening heeft geen tekeningnummer.
    -> Junction_3
Junction_3
    -> Junction_4
Junction_5
    -> Junction_6

Bookmark: uitval
Junction_12
    -> _Rejected_ (output)
Junction_20
    -> _Rejected_ (output)
Junction_14
    -> _Rejected_ (output)
Junction_18
    -> Uitval (output)
Junction_8
    -> _Rejected_ (output)
Junction_4
    -> Uitval (output)
Junction_6
    -> _Rejected_ (output)
Junction_2
    -> Uitval (output)
Uitval (output)
Junction_10
    -> _Rejected_ (output)
_Rejected_ (output)

Bookmark: bepalen fase
ListIndexer_fase_2
    INDEX = 8
    PREFIX = fase
    LIST_ATTR = _directory{}
    -> StringSearcher_fase
    <REJECTED> -> Junction_7
StringSearcher_fase
    STRING_TO_SEARCH = @Value(fase_directory)
    CASE = no
    MATCHED_PARTS_ATTR = fasesubexpressies
    REGEXP = ^\d{1,3}\s(\w{3,4})
    MATCHED -> ListIndexer_2
    NOT_MATCHED -> AttributeCreator_geenFase_revisie
ListIndexer_2
    INDEX = 0
    PREFIX = fase
    LIST_ATTR = fasesubexpressies{}
    -> AttributeValueMapper_fase
    <REJECTED> -> Junction_13
AttributeValueMapper_fase
    VAL_ATTR = _fase
    LUT = VUZ,2,LVUZ,3,GUZ,4,DUZ,5,WUZ,6
    DIRECTION = Forward (Source To Destination)
    SRC = fasepart
    -> ListIndexer_revisie_2
Junction_13
    -> Junction_14
AttributeCreator_geenFase_revisie
    ATTR_TABLE = SET_TO uitvalreden = Tekening heeft geen fase.
    -> Junction_17
Junction_17
    -> Junction_18
Junction_7
    -> Junction_8

Bookmark: bepalen revisie indien aanwezig; anders op 1 zetten
ListIndexer_revisie_2
    INDEX = 9
    PREFIX = revisie
    LIST_ATTR = _directory{}
    -> StringSearcher_revisie
    <REJECTED> -> Junction_19
StringSearcher_revisie
    STRING_TO_SEARCH = @Value(revisie_directory)
    MATCHED_RESULT_ATTR = _revisie
    CASE = no
    REGEXP = (\d{1,2})$
    MATCHED -> StringSearcher_revisie_MATCHED_-__AttributeManager
    NOT_MATCHED -> AttributeCreator_revisie1
AttributeCreator_revisie1
    ATTR_TABLE = SET_TO _revisie = 1
    -> StringSearcher_revisie_MATCHED_-__AttributeManager
StringSearcher_revisie_MATCHED_-__AttributeManager: Junction
    -> AttributeManager
Junction_19
    -> Junction_20

FME custom transformer ContourReconstructor
Maakt plancontouren aan aan de hand van aangeleverde plangrenzen.
    clippen op gemeentegrens
    stroken van arcs 
    snappen van edges en vertices binnen 5 meter 
    vormen van polyginen uit lines, arcs en ellipses 
    verwijderen binnengrenzen 
    verwijderen polygonen zonder oppervlakte 
    aggregeren naar oorspronkelijk bestandsnaam + -pad 
    ophalen projectmetadata + bepalen van uitval

Parameters:
- AUTOCAD_SOURCE_FILENAME = @Value(autocad_source_filename)   # Autocad Source Filename
- _FASE = @Value(_fase)   # Fase
- _GEBIEDCODE = @Value(_gebiedcode)   # Gebiedcode
- _MATCHED_RECORDS = @Value(_matched_records)   # Matched Records
- _REVISIE = @Value(_revisie)   # Revisie
- _TEKENINGNUMMER = @Value(_tekeningnummer)   # Tekeningnummer
- _TEKENINGPAD = @Value(_tekeningpad)   # Tekeningpad

AutoCadFeatures (input)
    -> AttributeKeeper
AttributeKeeper
    KEEP_ATTRS = autocad_source_filename
    -> Clipper [CLIPPEE]
Gemeente (input)
    -> Clipper [CLIPPER]
Initiator (input)
    -> AttributeRemover
AttributeRemover
    REMOVE_ATTRS = autocad_source_filename
    -> DuplicateFilter
DuplicateFilter
    INPUT_ORDERED_CHOICE = No
    KEYATTR = _tekeningpad
    UNIQUE -> FeatureMerger [REQUESTOR]
Note: Bepalen van tekeningen zonder / gereconstrueerde contour / en ophalen projectmetadata. / Match op basis van oorspronkeliijke / bestandsnaam + folder van de / autocad-tekening.
FeatureMerger
    PROCESS_DUPS = No
    JOIN_KEYS = @Value(_tekeningpad) @Value(autocad_source_filename) AUTO
    SUPPLIERS_FIRST = No
    REJECT_NULL_MISSING_KEYS = No
    MERGE_TYPE = Geometry
    MERGED -> AttributeManager_2
    UNMERGED_REQUESTOR -> AttributeCreator_geenFase_revisie
    <REJECTED> -> Junction_3
AttributeCreator_geenFase_revisie
    ATTR_TABLE = SET_TO _opmerking = Bij deze uitzending kon geen contour worden gevormd.
    -> AttributeManager_2
AttributeManager_2
    ATTR_TABLE = REMOVE _matched_records
    -> Uit (output)
Uit (output)
Junction_3
    -> Junction_4

Bookmark: waar nodig vormen van polygonen en aggregeren naaroorspronkelijke bestandsnaam
Note: clippen op gemeentegrens
Clipper
    MEASURE_TYPE = Continuous
    BOUNDARY_CASES = Treat as Inside
    CLIPPED_ATTR = _clipped
    MISSING_VAL_MODE = Compute
    CREATE_AGGREGATES = Yes
    VAL_SOURCE = Clippee Only
    CLIP_TYPE = Single Clipper
    LINES_AS_SEGMENTS = No
    PRESERVE_CLIPPEE_EXTENTS = No
    INSIDE -> ArcStroker
    <REJECTED> -> Junction_11
ArcStroker
    STROKE_CHOICE = Number of Interpolated Edges
    NUM = 0
    MAKE_POLY = No
    STROKED -> GeometryFilter
    <REJECTED> -> Junction
GeometryFilter
    GEOM_PORT_NAMES = Line Arc Area Ellipse
    BREAK_AGG = No
    LINE -> AreaBuilder
    ARC -> AreaBuilder
    AREA -> Dissolver
    ELLIPSE -> AreaBuilder
Note: per oosrspronkelijke autocadtekening
AreaBuilder
    CONNECT_Z_MODE = First Wins
    ALLOW_CYCLES = No
    SNAPTYPE_PARAM = Vertex Snapping
    GROUP_BY = autocad_source_filename
    CONSIDER_NODE_ELEVATION = no
    CHECK_CURVE_DIRECTION = No
    DONUT_CREATION = NO
    POLY_ACCUM_ATTRS_NAME = Use Attributes From One Feature
    SNAP_TOLERANCE = 5
    LINES_AS_SEGMENTS = No
    AREA -> Dissolver
    <REJECTED> -> Junction_9
Note: per oosrspronkelijke autocadtekening
Dissolver
    CONNECT_Z_MODE = First Wins
    GROUP_BY = autocad_source_filename
    NO_OVRLP = No
    ACCUM_INPUT_ATTRS = Use Attributes From One Feature
    DEAGGREGATE_INPUT = Yes
    AREA -> AreaCalculator
    <REJECTED> -> Junction_7
Note: oppervlakte > 0?
AreaCalculator
    AREA_TYPE = Plane Area
    AREA_ATTR = _area
    MULT = 1
    -> Tester_oppervlakte
    <REJECTED> -> Junction_5
Tester_oppervlakte
    TEST_DESCRIPTION = ""
    BOOL_OP = OR
    TEST_MODE = Automatic
    TEST_CLAUSE = TEST @Value(_area) > 0
    PASSED -> Aggregator
Note: per oosrspronkelijke autocadtekening
Aggregator
    GROUP_BY = autocad_source_filename
    AGGREGATE_TYPE = Homogeneous Collection (If Possible)
    ORDERED = No
    MODE = Geometry - Assemble One Level
    SEP = ,
    ACCUM_ATTRS_NAME = Use Attributes From One Feature
    AGGREGATE -> FeatureMerger [SUPPLIER]
Junction_5
    -> Junction_6
Junction_7
    -> Junction_8
Junction_9
    -> Junction_10
Junction
    -> Junction_2
Junction_11
    -> Junction_12

Bookmark: _rejected_
Junction_6
    -> _Rejected_ (output)
Junction_8
    -> _Rejected_ (output)
Junction_10
    -> _Rejected_ (output)
Junction_2
    -> _Rejected_ (output)
Junction_12
    -> _Rejected_ (output)
Junction_4
    -> _Rejected_ (output)
_Rejected_ (output)

FME custom transformer GUIDGenerator
Creates an ESRI GUID ID by creating a UUID enclosed by curly {}.
Input Ports
    Input
Accepts all types of features
    Output Ports
    Output
Returns all features with an additional GFID attribute

INPUT (input)
    -> UUIDGENERATOR_2
Note: Create UUID
UUIDGENERATOR_2: UUIDGenerator
    UUID_ATTR = GFID
    -> CONCATENATOR_2
Note: Enclose the UUID by {}
CONCATENATOR_2: StringConcatenator
    VAL_ATTR = GFID
    PARM_LINE = {@Value(GFID)}
    ACTION = Create New Attribute
    -> OUTPUT (output)
OUTPUT (output)
